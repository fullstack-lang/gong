# IBM Rational DOORS, 25 April 2017

# Specification: MODULE-1

## PUID-1: Requirement-1
- IE Object Type: Requirement
- Relation Type -> PUID-2

## PUID-2: Requirement-2
- IE Object Type: Requirement
