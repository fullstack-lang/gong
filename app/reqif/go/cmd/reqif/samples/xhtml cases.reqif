# Example ReqIF with Specification and XHTML Table

# Specification: Sample Specification

## _spec-object-1: Sample Requirement 1
| Main Table Title |  |  |  |
| --- | --- | --- | --- |
| Header 1 | Header 2 | Header 3 | Header 4 |
| Data A1 | Data B1 | Data C1 | Data D1 |
| Data A2 | Data B2 | Data C2 | Data D2 |
| Data A3 | Data B3 | Data C3 | Data D3 |

## _spec-object-2: Sample Requirement 2
| Header 1 | Header 2 | Header 3 | Header 4 | Header 5 |
| --- | --- | --- | --- | --- |
| R1-C1 | R1-C2 | R1-C3 | R1-C4 | R1-C5 |
| R2-C1 | R2-C2 | R2-C3 | R2-C4 | R2-C5 |
| R3-C1 | R3-C2 | R3-C3 | R3-C4 | R3-C5 |
